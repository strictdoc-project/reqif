# Beispiel einer ReqIF-Datei
Author: Mathilda Musterfrau

# Specification: System zur Erkennung von Waldbränden

## R1: Überwachung der Bodentemperatur
- Das System soll die Bodentemperatur überwachen.
- Ableitungsbeziehung Anforderung -> erkennungFeuer

### erkennungFeuer: Erkennung von Feuer
- Das System soll den Ausbruch von Feuer melden.
