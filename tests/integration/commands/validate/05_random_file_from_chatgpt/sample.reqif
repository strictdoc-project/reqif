# Specification: System-Level Requirements

## RQ1
- The coffee machine should support multiple brewing options, such as espresso, cappuccino, and latte.

## RQ2
- The coffee machine should have a water reservoir with a capacity of at least 1 liter.

## RQ3
- The coffee machine should allow users to adjust the grinding settings for different coffee beans.

## RQ4
- Users should be able to select the desired brew strength, such as strong or mild.

## RQ5
- The coffee machine should have a milk frothing functionality to prepare beverages that require frothed milk.

## RQ6
- The coffee machine should have an intuitive user interface with easy-to-use controls and a display for status and settings.

## RQ7
- The coffee machine should have features to facilitate easy cleaning and maintenance, such as removable parts and self-cleaning functionality.

## RQ8
- The coffee machine should have a power-saving mode that automatically turns off the machine after a period of inactivity.

## RQ9
- The coffee machine should be compatible with standard coffee capsules or pods available in the market.

## RQ10
- The coffee machine should provide informative error messages and handle exceptions gracefully.
