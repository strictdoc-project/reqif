# Example: Extract requirement text

# Specification: System requirements

## R1: Login

### REQ-1: Password length
The system shall reject passwords shorter than 12 characters.

### REQ-2: Failed logins
The system shall lock an account after:
- 5 failed login attempts, or
- an administrator request.
