# IBM Rational DOORS, 12 October 2018

# Specification: AMR Standards Documents
- ReqIF.Description: References to external governance standards
- ReqIF.Name: AMR Standards Documents

## 1: Carbon Trust Standard

## 2: CRC and CCA

## 3: Picture or Whitepaper
