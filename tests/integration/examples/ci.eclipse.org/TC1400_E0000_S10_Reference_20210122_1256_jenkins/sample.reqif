# TC 1400 'Internal Table'

# Specification

## R1: Obj1 (TC1400 SpecObjectType Regular)

### R2: Obj1.1 (TC1400 SpecObjectType Regular)

#### R3: TableObj1.1.1 (TC1400 SpecObjectType Internal Table)
Changed name
- Revision: 3

#### R4: TableObj1.1.2 (TC1400 SpecObjectType Internal Table)
Changed name in order to comply to company naming conventions
- Revision: 20

#### R5: TableObj1.1.3 (TC1400 SpecObjectType Internal Table)
initial revision
- Revision: 1
