# Documentation export by StrictDoc

# Specification: Sample document

## R1: Section 1

### R2: Section 1.1

#### R3: Requirement A
The system shall do A.

#### R4: Requirement B
The system shall do B.

#### R5: Requirement C
The system shall do C.

## R6: Section 2

### R7: Section 2.1

#### R8: Requirement A
The system shall do A.

#### R9: Requirement B
The system shall do B.

#### R10: Requirement C
The system shall do C.

## R11: Section 3

### R12: Section 3.1

#### R13: Section 3.1.1

##### R14: Section 3.1.1.1

###### R15: Requirement A
The system shall do A.

###### R16: Section 3.1.1.1.2 (section between requirements)

###### R17: Requirement B
The system shall do B.

## R18: Section 4
